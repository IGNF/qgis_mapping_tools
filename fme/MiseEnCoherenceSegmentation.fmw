FME workspace MiseEnCoherenceSegmentation.fmw

Parameters:
- chemin_father = /Volumes/Viso/DATA_EXPERIMENTATION_ARTIFICIALISATION_65/DATA_PREPARATION_LOUDENVIELLE/TEST/fusionPasse2-10-C3_CROP.shp   # chemin du père
- chemin_child = /Volumes/Viso/DATA_EXPERIMENTATION_ARTIFICIALISATION_65/DATA_PREPARATION_LOUDENVIELLE/TEST/fusionPasse2-06-C4_CROP.shp   # chemin du fils
- chemin_sortie = /Volumes/Viso/DATA_EXPERIMENTATION_ARTIFICIALISATION_65/DATA_PREPARATION_LOUDENVIELLE/TEST   # Destination Esri Shape Directory

Readers:
- SHAPE_1: SHAPE from $(chemin_father)
- SHAPE_2: SHAPE from $(chemin_child)

Writers:
- SHAPE_3: SHAPE to $(chemin_sortie)

father (reader SHAPE_1)
    attributes: Valeur number(10,0)
    -> AttributeCopier
AttributeCopier
    ATTR_LIST = fme_basename,resultat,"",Valeur,resultatValeur,""
    -> Counter
Counter
    SCOPE = Local
    START = 1
    DOMAIN = counter
    CNT_ATTR = Ident
    -> Id_Pere
Id_Pere: StringConcatenator
    PARM_LINE = P@Value(Ident)
    VAL_ATTR = Id_Pere
    -> Mise_a_plat
child (reader SHAPE_2)
    attributes: Valeur number(10,0)
    -> Surf_Fils_Avant
Surf_Fils_Avant: AreaCalculator
    AREA_ATTR = Surf_Avant
    AREA_TYPE = Plane Area
    MULT = 1
    -> Counter_2
Counter_2
    SCOPE = Local
    START = 1
    DOMAIN = counter
    CNT_ATTR = Ident
    -> Id_Fils
Id_Fils: StringConcatenator
    PARM_LINE = F@Value(Ident)
    VAL_ATTR = Id_Fils
    -> Mise_a_plat
    -> Jointure_Pere_Fils [input 1]
Mise_a_plat: AreaOnAreaOverlayer
    AREA -> Surf_Fils_Apres
Surf_Fils_Apres: AreaCalculator
    AREA_ATTR = Surf_Apres
    AREA_TYPE = Plane Area
    MULT = 1
    -> Ratio
Ratio: ExpressionEvaluator
    VAL_ATTR = Ratio
    EXPRESSION = @Value(Surf_Apres)*1./@Value(Surf_Avant)
    -> Ratio_sup_0.25
Ratio_sup_0.25: Tester
    TEST_MODE = Automatic
    TEST_DESCRIPTION = ""
    BOOL_OP = OR
    TEST_CLAUSE = TEST @Value(Ratio) > 0,25
    PASSED -> Jointure_Pere_Fils [input 2]
Jointure_Pere_Fils: FeatureMerger
    PROCESS_DUPS = No
    MERGE_TYPE = Attributes Only
    SUPPLIERS_FIRST = No
    JOIN_KEYS = @Value(Id_Fils) @Value(Id_Fils) AUTO
    SUPPLIER_PREFIX_DUMMY = YES
    MERGED -> AttributeKeeper
AttributeKeeper
    KEEP_ATTRS = Id_Fils,resultatValeur,resultat,Id_Pere
    -> AttributeCreator
AttributeCreator
    ATTR_LIST = Nb_Fils,1
    -> Dissolver
Dissolver
    GROUP_BY = Id_Pere
    DIS_ATTR = Nb_Fils
    LIST_NAME = Liste_Fils
    NO_OVRLP = No
    ACCUM_INPUT_ATTRS = No
    AREA -> ListConcatenator
ListConcatenator
    VAL_ATTR = Fils
    SEP = /
    LIST_ATTR = Liste_Fils{}.Id_Fils
    DROP_EMPTY_PARTS = No
    -> OUT (writer SHAPE_3)
OUT (writer SHAPE_3)
    attributes: Valeur number(30,0)
